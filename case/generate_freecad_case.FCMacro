# -*- coding: utf-8 -*-
# ============================================================================
# ALESTE 520EX — Native FreeCAD 1.1 Parametric 3D Case & Staggered Switch Plate
# ============================================================================
# Generates:
#   - case/Aleste520_Case.FCStd          (Full multi-body FreeCAD Assembly + Interlocking Quadrants)
#   - case/Aleste520_Bottom_Case.FCStd   (Standalone 1-Piece Bottom Case Tray, DFM >= 2.5mm walls)
#   - case/Aleste520_Top_Cover.FCStd     (Standalone 1-Piece Sloped Top Cover, DFM >= 2.5mm walls)
#   - case/Aleste520_Switch_Plate.FCStd  (Standalone 1.5mm Staggered Cherry MX Switch Plate + 6.25U Stabilizers)
#   - case/Aleste520_Case.step           (ISO 10303-21 STEP CAD Exchange File)
# ============================================================================

import os
import FreeCAD as App
import Part
import Mesh

out_dir = os.path.dirname(os.path.abspath(__file__)) if "__file__" in globals() else os.path.abspath("case")

# --- 1. Reference Motherboard & Enclosure Parameters (mm) ---
pcb_w          = 400.9
pcb_d          = 280.5
pcb_t          = 1.6
pcb_x_min      = 16.0
pcb_y_min      = 19.5
pcb_y_max      = 300.0

wall_t         = 4.0     # Outer structural wall thickness (4.0 mm >= JLCPCB SLA DFM minimum)
floor_t        = 4.0     # Base floor thickness (4.0 mm for anti-warping on 416x296mm SLA)
clearance      = 3.5     # Internal perimeter clearance around PCB
standoff_h     = 8.0     # Height of M3 motherboard standoffs above floor

ext_w          = pcb_w + 2 * (wall_t + clearance)  # 415.9 mm
ext_d          = pcb_d + 2 * (wall_t + clearance)  # 295.5 mm
lower_h        = 28.5    # Bottom tray wall height
upper_front_h  = 12.0    # Top cover front edge height
upper_rear_h   = 34.0    # Top cover rear edge height

mid_x          = ext_w / 2.0  # 207.95 mm quadrant X split plane
mid_y          = ext_d / 2.0  # 147.75 mm quadrant Y split plane

kb_origin_x    = 24.0    # CAD X start of keyboard bezel
kb_origin_y    = 18.0    # CAD Y start of keyboard bezel
kb_w           = 358.0   # Keyboard PCB & plate width
kb_d           = 122.0   # Keyboard PCB & plate depth
plate_t        = 2.0     # 2.0mm thick for 3D-printed plate DFM (1.5mm at switch snap rim)

def pcb_to_cad_x(x_pcb):
    return wall_t + clearance + (x_pcb - pcb_x_min)

def pcb_to_cad_y(y_pcb):
    return wall_t + clearance + (pcb_y_max - y_pcb)

# 11 M3 Mounting Holes from board/Aleste520v4.kicad_pcb: (x_pcb, y_pcb, is_kb_antiflex)
mh_coords = [
    ( 23.5,  24.0, False),  # MH1  Rear-Left
    (215.0,  24.0, False),  # MH2  Rear-Center-Left
    (273.0,  24.0, False),  # MH3  Rear-Center-Right
    (411.5,  24.0, False),  # MH4  Rear-Right
    ( 41.0, 130.0, True ),  # MH5  Mid-Left (Keyboard Rear Anti-Flex Pillar)
    (220.0, 131.0, True ),  # MH6  Center (Keyboard Center Anti-Flex Pillar)
    (409.5, 148.0, True ),  # MH7  Mid-Right (Keyboard Right Anti-Flex Pillar)
    ( 23.5, 286.5, True ),  # MH8  Front-Left (Keyboard Front Anti-Flex Pillar)
    (148.0, 285.5, True ),  # MH9  Front-Center-Left (Keyboard Spacebar Anti-Flex Pillar)
    (283.5, 286.5, True ),  # MH10 Front-Center-Right (Keyboard Front Anti-Flex Pillar)
    (406.5, 256.5, True ),  # MH11 Front-Right L-Wing (Keyboard Front-Right Anti-Flex Pillar)
]

# 10 M3 Anti-Flex Mounting Holes on keyboard/Aleste520_Keyboard.kicad_pcb
kb_mh_coords = [
    (  4.0,   4.0), (124.0,   4.0), (244.0,   4.0), (354.0,   4.0),
    (  4.0,  61.0), (258.0, 113.5), (265.0,  26.0), (354.0,  61.0),
    (  4.0, 118.0), (354.0, 118.0)
]

# 83 Staggered Switch Centers (x_kb, y_kb, width_u) matching keyboard/Aleste520_Keyboard.kicad_pcb
staggered_switches = [
    ( 20.00,  26.00, 1.00), ( 44.00,  26.00, 1.25), ( 67.80,  26.00, 1.25), ( 91.60,  26.00, 1.25),
    (115.40,  26.00, 1.25), (139.20,  26.00, 1.25), (168.00,  26.00, 1.25), (191.80,  26.00, 1.25),
    (215.60,  26.00, 1.25), (239.40,  26.00, 1.25), (339.50,  26.00, 1.00),
    ( 20.00,  43.50, 1.00), ( 39.05,  43.50, 1.00), ( 58.10,  43.50, 1.00), ( 77.15,  43.50, 1.00),
    ( 96.20,  43.50, 1.00), (115.25,  43.50, 1.00), (134.30,  43.50, 1.00), (153.35,  43.50, 1.00),
    (172.40,  43.50, 1.00), (191.45,  43.50, 1.00), (210.50,  43.50, 1.00), (229.55,  43.50, 1.00),
    (248.60,  43.50, 1.00), (281.00,  43.50, 1.00), (300.05,  43.50, 1.00), (319.10,  43.50, 1.00),
    (339.50,  43.50, 1.00),
    ( 24.76,  61.00, 1.50), ( 48.58,  61.00, 1.00), ( 67.63,  61.00, 1.00), ( 86.68,  61.00, 1.00),
    (105.73,  61.00, 1.00), (124.78,  61.00, 1.00), (143.83,  61.00, 1.00), (162.88,  61.00, 1.00),
    (181.93,  61.00, 1.00), (200.98,  61.00, 1.00), (220.03,  61.00, 1.00), (239.08,  61.00, 1.00),
    (258.13,  61.00, 1.00), (281.00,  61.00, 1.00), (300.05,  61.00, 1.00), (319.10,  61.00, 1.00),
    (339.50,  61.00, 1.00),
    ( 27.14,  78.50, 1.75), ( 53.34,  78.50, 1.00), ( 72.39,  78.50, 1.00), ( 91.44,  78.50, 1.00),
    (110.49,  78.50, 1.00), (129.54,  78.50, 1.00), (148.59,  78.50, 1.00), (167.64,  78.50, 1.00),
    (186.69,  78.50, 1.00), (205.74,  78.50, 1.00), (224.79,  78.50, 1.00), (243.84,  78.50, 1.00),
    (281.00,  78.50, 1.00), (300.05,  78.50, 1.00), (319.10,  78.50, 1.00), (339.50,  78.50, 1.00),
    ( 29.52,  96.00, 2.00), ( 58.10,  96.00, 1.00), ( 77.15,  96.00, 1.00), ( 96.20,  96.00, 1.00),
    (115.25,  96.00, 1.00), (134.30,  96.00, 1.00), (153.35,  96.00, 1.00), (172.40,  96.00, 1.00),
    (191.45,  96.00, 1.00), (210.50,  96.00, 1.00), (229.55,  96.00, 1.00), (253.36,  96.00, 1.50),
    (281.00,  96.00, 1.00), (300.05,  96.00, 1.00), (319.10,  96.00, 1.00), (339.50,  96.00, 1.00),
    ( 24.76, 113.50, 1.50), ( 50.95, 113.50, 1.25), ( 74.76, 113.50, 1.25),
    (153.65, 113.50, 6.25), (227.47, 113.50, 1.50)
]

# ============================================================================
# BUILD PART 1: BOTTOM CASE TRAY (DFM-Compliant: all walls & ribs >= 2.5mm)
# ============================================================================
def build_bottom_case():
    outer = Part.makeBox(ext_w, ext_d, lower_h)
    inner = Part.makeBox(ext_w - 2*wall_t, ext_d - 2*wall_t, lower_h, App.Vector(wall_t, wall_t, floor_t))
    tray = outer.cut(inner)

    # Rear I/O Connector Cutouts + PicoPSU 12V DC Jack & Power Switch
    # All cutouts start at >= Z = 11.5 mm and stop at <= Z = 25.0 mm (or open cleanly at the top rim Z = 28.5mm)
    # so there are NO thin horizontal bridges (< 3.5 mm) at the top or bottom of the rear wall!
    rear_z = floor_t + standoff_h + pcb_t  # 13.6 mm
    cutouts = []
    # Open rear connector cutouts all the way through the top rim (lower_h + 2.0) so there is zero thin bridge above them!
    cut_h = lower_h + 5.0
    cutouts.append(Part.makeBox(32.0, wall_t + 4.0, cut_h, App.Vector(pcb_to_cad_x(38.6) - 16.0, ext_d - wall_t - 2.0, rear_z - 1.5)))
    cutouts.append(Part.makeBox(44.0, wall_t + 4.0, cut_h, App.Vector(pcb_to_cad_x(60.0) - 10.0, ext_d - wall_t - 2.0, rear_z - 1.5)))
    cutouts.append(Part.makeBox(85.5, wall_t + 4.0, cut_h, App.Vector(pcb_to_cad_x(112.5), ext_d - wall_t - 2.0, rear_z - 2.5)))
    cutouts.append(Part.makeBox(18.0, wall_t + 4.0, cut_h, App.Vector(pcb_to_cad_x(211.0) - 9.0, ext_d - wall_t - 2.0, rear_z - 1.5)))
    cutouts.append(Part.makeBox(47.0, wall_t + 4.0, cut_h, App.Vector(pcb_to_cad_x(225.5), ext_d - wall_t - 2.0, rear_z - 2.5)))
    cutouts.append(Part.makeBox(18.0, wall_t + 4.0, cut_h, App.Vector(pcb_to_cad_x(309.0) - 9.0, ext_d - wall_t - 2.0, rear_z - 1.5)))
    # PicoPSU 12V DC Barrel Jack (D=11.4mm centered at Z = 18.0mm -> 4.7mm below top rim!)
    dc_jack = Part.makeCylinder(5.7, wall_t + 4.0, App.Vector(pcb_to_cad_x(365.0), ext_d + 2.0, 18.0), App.Vector(0, -1, 0))
    cutouts.append(dc_jack)
    # Rear Power Rocker Switch (open top U-slot so Top Cover closes over it with zero thin bridge)
    cutouts.append(Part.makeBox(19.4, wall_t + 4.0, cut_h, App.Vector(pcb_to_cad_x(380.0), ext_d - wall_t - 2.0, rear_z - 1.0)))

    # Side ventilation slots (5.0mm wide, spaced every 16.0mm -> 11.0mm solid pillar between slots, Z = 9.0..23.0 -> 5.5mm solid top rim!)
    vy = 45.0
    while vy <= ext_d - 45.0:
        if abs(vy - mid_y) > 18.0:
            cutouts.append(Part.makeBox(wall_t + 4.0, 5.0, 14.0, App.Vector(-2.0, vy, 9.0)))
            cutouts.append(Part.makeBox(wall_t + 4.0, 5.0, 14.0, App.Vector(ext_w - wall_t - 2.0, vy, 9.0)))
        vy += 16.0

    tray = tray.cut(Part.makeCompound(cutouts))

    adds = []
    # Solid 4.0mm wide x 5.0mm tall anti-warp floor grid ribs (all >= 4.0mm thick for JLCPCB DFM)
    for ry in (65.0, 147.75, 235.0):
        adds.append(Part.makeBox(ext_w - 2*wall_t, 4.0, 5.0, App.Vector(wall_t, ry - 2.0, floor_t)))
    for rx in (105.0, 207.95, 310.0):
        adds.append(Part.makeBox(4.0, ext_d - 2*wall_t, 5.0, App.Vector(rx - 2.0, wall_t, floor_t)))

    # 11 M3 Motherboard Standoffs (outer R = 5.0mm, inner hole R = 1.5mm -> 3.5mm solid wall thickness!)
    # + 7 Coaxial Upper Anti-Flex Keyboard Support Columns (outer R = 4.5mm, inner R = 1.6mm -> 2.9mm wall thickness!)
    for x_pcb, y_pcb, is_kb in mh_coords:
        cx = pcb_to_cad_x(x_pcb)
        cy = pcb_to_cad_y(y_pcb)
        cone = Part.makeCone(5.5, 4.5, standoff_h, App.Vector(cx, cy, floor_t))
        hole = Part.makeCylinder(1.5, standoff_h + 1.0, App.Vector(cx, cy, floor_t))
        adds.append(cone.cut(hole))
        if is_kb:
            z_col = floor_t + standoff_h + pcb_t
            col_outer = Part.makeCylinder(4.5, 16.5, App.Vector(cx, cy, z_col))
            col_inner = Part.makeCylinder(1.6, 17.0, App.Vector(cx, cy, z_col - 0.2))
            adds.append(col_outer.cut(col_inner))

    # 4 PicoPSU DC-DC Mounting Bosses (outer R = 4.2mm, inner R = 1.5mm -> 2.7mm wall thickness!)
    for px in (pcb_to_cad_x(320.0), pcb_to_cad_x(390.0)):
        for py in (pcb_to_cad_y(294.0), pcb_to_cad_y(274.0)):
            boss = Part.makeCylinder(4.2, standoff_h, App.Vector(px, py, floor_t))
            bhole = Part.makeCylinder(1.5, standoff_h + 1.0, App.Vector(px, py, floor_t))
            adds.append(boss.cut(bhole))

    for a in adds:
        tray = tray.fuse(a)
    return tray

# ============================================================================
# BUILD PART 2: SLOPED TOP COVER (DFM-Compliant: all walls & ribs >= 3.0mm)
# ============================================================================
def make_wedge(w, d, h_front, h_rear, y_flat_rear=140.0):
    pts = [
        App.Vector(0, 0, 0),
        App.Vector(0, d, 0),
        App.Vector(0, d, h_rear),
        App.Vector(0, d - y_flat_rear, h_rear),
        App.Vector(0, 0, h_front),
        App.Vector(0, 0, 0)
    ]
    wire = Part.makePolygon(pts)
    face = Part.Face(wire)
    return face.extrude(App.Vector(w, 0, 0))

def build_top_cover():
    outer = make_wedge(ext_w, ext_d, upper_front_h, upper_rear_h, 140.0)
    inner = make_wedge(ext_w - 2*wall_t, ext_d - 2*wall_t, upper_front_h - 4.0, upper_rear_h - 4.0, 140.0 - wall_t)
    inner.translate(App.Vector(wall_t, wall_t, -0.1))
    cover = outer.cut(inner)

    # Recessed Keyboard Bezel Opening (358.0 x 122.0 mm)
    kb_cut = Part.makeBox(kb_w, kb_d, upper_rear_h + 10.0, App.Vector(kb_origin_x, kb_origin_y, -2.0))
    cover = cover.cut(kb_cut)

    # Status LED Holes (D=3.2mm, spaced 12mm apart)
    led1 = Part.makeCylinder(1.6, upper_rear_h + 10.0, App.Vector(kb_origin_x + kb_w + 12.0, kb_origin_y + 100.0, -2.0))
    led2 = Part.makeCylinder(1.6, upper_rear_h + 10.0, App.Vector(kb_origin_x + kb_w + 24.0, kb_origin_y + 100.0, -2.0))
    cover = cover.cut(led1).cut(led2)

    # Anti-Flex Perimeter Ledge (5.0mm wide, 8.0mm tall) around Keyboard Bay
    ledge_w = 5.0
    ledge_z = 8.0
    ledge_outer = Part.makeBox(kb_w + 2*ledge_w, kb_d + 2*ledge_w, ledge_z, App.Vector(kb_origin_x - ledge_w, kb_origin_y - ledge_w, 0))
    ledge_inner = Part.makeBox(kb_w - 6.0, kb_d - 6.0, ledge_z + 2.0, App.Vector(kb_origin_x + 3.0, kb_origin_y + 3.0, -1.0))
    ledge = ledge_outer.cut(ledge_inner)
    cover = cover.fuse(ledge)

    # Transverse Anti-Flex Support Rib in the 13.0mm divider channel between Alpha block and Numpad (x_kb = 269.5, width 3.5mm)
    kx = kb_origin_x + 269.5
    rib_x = Part.makeBox(3.5, kb_d, ledge_z - 1.5, App.Vector(kx - 1.75, kb_origin_y, 0))
    cover = cover.fuse(rib_x)

    # 3 Longitudinal Anti-Flex Support Ribs between staggered key rows (width 3.0mm >= DFM minimum)
    for y_kb_rib in (34.75, 69.75, 104.75):
        ky = kb_origin_y + (kb_d - y_kb_rib)
        rib_y = Part.makeBox(kb_w, 3.0, ledge_z - 1.5, App.Vector(kb_origin_x, ky - 1.5, 0))
        cover = cover.fuse(rib_y)

    return cover

# ============================================================================
# BUILD PART 3: STAGGERED CHERRY MX SWITCH PLATE (83 Cutouts + 6.25U Stabilizers)
# ============================================================================
def build_switch_plate():
    plate = Part.makeBox(kb_w, kb_d, plate_t)
    sw_cut = 14.0
    holes = []
    for x_kb, y_kb, wu in staggered_switches:
        cx = x_kb
        cy = kb_d - y_kb
        holes.append(Part.makeBox(sw_cut, sw_cut, plate_t + 2.0, App.Vector(cx - sw_cut/2.0, cy - sw_cut/2.0, -1.0)))
        if wu >= 6.0:
            for sx_off in (-50.0, 50.0):
                holes.append(Part.makeBox(6.8, 13.8, plate_t + 2.0, App.Vector(cx + sx_off - 3.4, cy - 6.9, -1.0)))

    for mx, my in kb_mh_coords:
        holes.append(Part.makeCylinder(1.6, plate_t + 2.0, App.Vector(mx, kb_d - my, -1.0)))

    plate = plate.cut(Part.makeCompound(holes))
    return plate

# ============================================================================
# HELPER: SPLIT SHAPE INTO 4 INTERLOCKING QUADRANTS WITH CAPTIVE-NUT JOINERS
# (Applied ONLY to the 256x256mm Quadrant versions so Whole versions remain 100% solid!)
# ============================================================================
def split_into_interlocking_quadrants(base_shape, is_bottom=True):
    shape = base_shape.copy()
    if is_bottom:
        # Add heavy-duty 14mm-wide x 8mm-tall Captive-Nut Joiner Blocks across mid_x and mid_y with >= 2.5mm walls
        j_adds = []
        j_cuts = []
        for ry in (65.0, 235.0):
            j_adds.append(Part.makeBox(64.0, 14.0, 7.5, App.Vector(mid_x - 24.0, ry - 7.0, floor_t)))
            j_cuts.append(Part.makeCylinder(1.6, 52.0, App.Vector(mid_x - 18.0, ry, floor_t + 3.8), App.Vector(1, 0, 0)))
            j_cuts.append(Part.makeBox(2.8, 5.65, 5.5, App.Vector(mid_x - 9.0, ry - 2.825, floor_t + 2.5)))
            j_cuts.append(Part.makeBox(24.0, 8.0, 5.5, App.Vector(mid_x + 8.0, ry - 4.0, floor_t + 2.5)))
        for rx in (105.0, 310.0):
            j_adds.append(Part.makeBox(14.0, 64.0, 7.5, App.Vector(rx - 7.0, mid_y - 24.0, floor_t)))
            j_cuts.append(Part.makeCylinder(1.6, 52.0, App.Vector(rx, mid_y - 18.0, floor_t + 3.8), App.Vector(0, 1, 0)))
            j_cuts.append(Part.makeBox(5.65, 2.8, 5.5, App.Vector(rx - 2.825, mid_y - 9.0, floor_t + 2.5)))
            j_cuts.append(Part.makeBox(8.0, 24.0, 5.5, App.Vector(rx - 4.0, mid_y + 8.0, floor_t + 2.5)))
        for a in j_adds:
            shape = shape.fuse(a)
        shape = shape.cut(Part.makeCompound(j_cuts))

    q1_box = Part.makeBox(mid_x, mid_y, 100.0, App.Vector(0, 0, -5.0))
    q2_box = Part.makeBox(mid_x + 5.0, mid_y, 100.0, App.Vector(mid_x, 0, -5.0))
    q3_box = Part.makeBox(mid_x, mid_y + 5.0, 100.0, App.Vector(0, mid_y, -5.0))
    q4_box = Part.makeBox(mid_x + 5.0, mid_y + 5.0, 100.0, App.Vector(mid_x, mid_y, -5.0))

    q1 = shape.common(q1_box)
    q2 = shape.common(q2_box)
    q3 = shape.common(q3_box)
    q4 = shape.common(q4_box)
    return q1, q2, q3, q4

print("Building DFM-Compliant Bottom Case, Top Cover, and Staggered Switch Plate B-Rep solids...")
bottom_shape = build_bottom_case()
top_shape    = build_top_cover()
plate_shape  = build_switch_plate()

bottom_q1, bottom_q2, bottom_q3, bottom_q4 = split_into_interlocking_quadrants(bottom_shape, True)
top_q1, top_q2, top_q3, top_q4             = split_into_interlocking_quadrants(top_shape, False)
plate_left  = plate_shape.common(Part.makeBox(kb_w/2.0, kb_d, 10.0, App.Vector(0, 0, -2.0)))
plate_right = plate_shape.common(Part.makeBox(kb_w/2.0 + 5.0, kb_d, 10.0, App.Vector(kb_w/2.0, 0, -2.0)))

# ============================================================================
# SAVE MAIN ASSEMBLY DOCUMENT: case/Aleste520_Case.FCStd
# ============================================================================
doc = App.newDocument("Aleste520_Case")

obj_bot = doc.addObject("Part::Feature", "Bottom_Case")
obj_bot.Label = "01_Bottom_Case_Tray"
obj_bot.Shape = bottom_shape

obj_plate = doc.addObject("Part::Feature", "Switch_Plate_1_5mm")
obj_plate.Label = "02_Keyboard_Switch_Plate_1_5mm"
plate_placed = plate_shape.copy()
plate_placed.translate(App.Vector(kb_origin_x, kb_origin_y, lower_h + 6.5))
obj_plate.Shape = plate_placed

obj_top = doc.addObject("Part::Feature", "Top_Cover")
obj_top.Label = "03_Top_Cover_Sloped_AntiFlex"
top_placed = top_shape.copy()
top_placed.translate(App.Vector(0, 0, lower_h))
obj_top.Shape = top_placed

grp = doc.addObject("App::DocumentObjectGroup", "Printable_Quadrants_256x256")
grp.Label = "04_Printable_Quadrants_256x256mm"
for qname, qlabel, qshape in [
    ("Bottom_Q1_FrontLeft",  "Bottom_Q1_FrontLeft",  bottom_q1),
    ("Bottom_Q2_FrontRight", "Bottom_Q2_FrontRight", bottom_q2),
    ("Bottom_Q3_RearLeft",   "Bottom_Q3_RearLeft",   bottom_q3),
    ("Bottom_Q4_RearRight",  "Bottom_Q4_RearRight",  bottom_q4),
    ("Top_Q1_FrontLeft",     "Top_Q1_FrontLeft",     top_q1),
    ("Top_Q2_FrontRight",    "Top_Q2_FrontRight",    top_q2),
    ("Top_Q3_RearLeft",      "Top_Q3_RearLeft",      top_q3),
    ("Top_Q4_RearRight",     "Top_Q4_RearRight",     top_q4),
    ("Plate_Left_Half",      "Plate_Left_Half",      plate_left),
    ("Plate_Right_Half",     "Plate_Right_Half",     plate_right),
]:
    qo = doc.addObject("Part::Feature", qname)
    qo.Label = qlabel
    qo.Shape = qshape
    grp.addObject(qo)

doc.recompute()
fcstd_main = os.path.join(out_dir, "Aleste520_Case.FCStd")
doc.saveAs(fcstd_main)
print("Saved:", fcstd_main)

step_path = os.path.join(out_dir, "Aleste520_Case.step")
Part.export([obj_bot, obj_plate, obj_top], step_path)
print("Saved:", step_path)

for fname, dname, shp in [
    ("Aleste520_Bottom_Case.FCStd",  "Aleste520_Bottom_Case",  bottom_shape),
    ("Aleste520_Top_Cover.FCStd",    "Aleste520_Top_Cover",    top_shape),
    ("Aleste520_Switch_Plate.FCStd", "Aleste520_Switch_Plate", plate_shape),
]:
    d = App.newDocument(dname)
    o = d.addObject("Part::Feature", dname)
    o.Label = dname
    o.Shape = shp
    d.recompute()
    p = os.path.join(out_dir, fname)
    d.saveAs(p)
    App.closeDocument(d.Name)
    print("Saved:", p)

# Export JLCPCB 3D print STEP & STL files
jlc_dir = os.path.join(out_dir, "jlcpcb_3dprint")
quad_dir = os.path.join(jlc_dir, "quadrants_256x256")
os.makedirs(jlc_dir, exist_ok=True)
os.makedirs(quad_dir, exist_ok=True)

for shp, out_base in [
    (bottom_shape, "1_Aleste520_Bottom_Case_Whole"),
    (top_shape,    "2_Aleste520_Top_Cover_Whole"),
    (plate_shape,  "3_Aleste520_Switch_Plate_1_5mm_Whole"),
]:
    s_copy = shp.copy()
    bb = s_copy.BoundBox
    s_copy.translate(App.Vector(-bb.XMin, -bb.YMin, -bb.ZMin))
    s_copy.exportStep(os.path.join(jlc_dir, out_base + ".step"))
    m = Mesh.Mesh()
    m.addFacets(s_copy.tessellate(0.08))
    m.write(os.path.join(jlc_dir, out_base + ".stl"))
    print("Exported DFM-clean:", out_base + ".stl & .step")

for qn, qshp in [
    ("Bottom_Q1_FrontLeft",  bottom_q1),
    ("Bottom_Q2_FrontRight", bottom_q2),
    ("Bottom_Q3_RearLeft",   bottom_q3),
    ("Bottom_Q4_RearRight",  bottom_q4),
    ("Top_Q1_FrontLeft",     top_q1),
    ("Top_Q2_FrontRight",    top_q2),
    ("Top_Q3_RearLeft",      top_q3),
    ("Top_Q4_RearRight",     top_q4),
    ("Plate_Left_Half",      plate_left),
    ("Plate_Right_Half",     plate_right),
]:
    s_copy = qshp.copy()
    bb = s_copy.BoundBox
    s_copy.translate(App.Vector(-bb.XMin, -bb.YMin, -bb.ZMin))
    m = Mesh.Mesh()
    m.addFacets(s_copy.tessellate(0.08))
    m.write(os.path.join(quad_dir, qn + ".stl"))

App.closeDocument(doc.Name)
print("All DFM-compliant FreeCAD & JLCPCB STL/STEP files generated successfully.")
